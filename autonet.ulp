/*
License info:

You're free to use and modify this ULP, but I want credit for being the person who created it. So, in other words, feel free to do what you want with this, but don't claim it as your own work. Give me credit where you use my source. If you fail to do so, I will be less likely to release my work for free. 

Also, I'm 23, poor, unemployed, and would really like the Professional version of EAGLE, or at least a commercial license for the Standard edition. If this program has reduced your development time and missed nets on boards, saving you money, (or increases the sales of your CAD software) feel free to help me get one of these licenses :)

And now for the disclaimer: If this program increases your development time, screws up your boards, et cetera, I'm not liable. And even if I were liable, I'm not worth enough to pursue. 

-Alan
alansamet@yahoo.com

*/

#usage "en: <b>RUN AutoNet [Instruction | NDLFileName];</b>\n\
<br>\
<br>\
<author><b>By Alan Samet</b></author>\
<br><a href=mailto:alansamet@yahoo.com>alansamet@yahoo.com</a>\
\n\
<p>This ULP connects pins to nets on a schematic. It's very useful if you need to map a bunch of IC pins to nets. </p>\
\n\
<p>For instance, say you have a microcontroller named IC1 with a few ports that you want to map to some nets; you plan to connect those nets\n\
to pins on a port header SV1. We'll say IC1 has an 8-pin port named PA. Since the pins can also serve as ADC inputs, the pins for PA are named:\n\
</p>\n\
<p>(ADC0)PA0\n\
<br>(ADC1)PA1\n\
... and so on\n\
</p>\n\
<p>You can do this easily by using the following syntax (argument 3 is the leader length, 4 is the offset or bend, 5 is the style (see SET documentation) and 6 is the net class):\n\
</p>\n\
<p>IC1.(ADC[0..7])PA[0..7] PINNETNAME[0..7] 0.3 0.1 1 default;\n\
<br>IC1.PB[0..7] PINNETNAME[8..15] 0.3 0.1 1 default;\n\
<br>IC1.PC[0..3],IC1.VCC PINNETNAME[16..19],+5V 0.3 0.1 1 default;\n\
<br>SV1.[1..50] PINNETNAME[1..50] 0.3 0.1 1 default;\n\
</p>\n\
<B>Net Definition Language Syntax:</B>\n\
\n\
<p>PinOrNetList1 PinOrNetList2 LeaderLength LeaderOffset BendStyle NetClassName;\n\
</p>\n\
<p>I recommend using a leaderlength of 0.3, leaderoffset of 0.1 and a bendstyle of 1. \n\
</p>\
<p>You can pass a single statement as an argument to this ULP or the path to a source NDL file</p>\
<b>License info:</b>\
<p>\
You're free to use and modify this ULP, but I want credit for being the person who created it. So, in other words, feel free to do what you want with this, but don't claim it as your own work. Give me credit where you use my source. If you fail to do so, I will be less likely to release my work for free. \
</p>\
<p>\
Also, I'm 23, poor, unemployed, and would really like the Professional version of EAGLE, or at least a commercial license for the Standard edition. If this program has reduced your development time and missed nets on boards, saving you money, (or increases the sales of your CAD software) feel free to help me get one of these licenses :)\
</p>\
<p>And now for the disclaimer: If this program increases your development time, screws up your boards, et cetera, I'm not liable. And even if I were liable, I'm not worth enough to pursue. \
</p>\
\
"

/*

By Alan Samet

This ULP connects pins to nets on a schematic. It's very useful if you need to map a bunch of IC pins to nets. 

For instance, say you have a microcontroller named IC1 with a few ports that you want to map to some nets; you plan to connect those nets
to pins on a port header SV1. We'll say IC1 has an 8-pin port named PA. Since the pins can also serve as ADC inputs, the pins for PA are named:

(ADC0)PA0
(ADC1)PA1
... and so on

You can do this easily by using the following syntax (argument 3 is the leader length, 4 is the offset or bend, 5 is the style (see SET documentation) and 6 is the net class):

IC1.(ADC[0..7])PA[0..7] PINNETNAME[0..7] 0.3 0.1 1 default;
IC1.PB[0..7] PINNETNAME[8..15] 0.3 0.1 1 default;
IC1.PC[0..3],IC1.VCC PINNETNAME[16..19],+5V 0.3 0.1 1 default;
SV1.[1..50] PINNETNAME[1..50] 0.3 0.1 1 default;

Net Definition Language Syntax:

PinOrNetList1 PinOrNetList2 LeaderLength LeaderOffset BendStyle NetClassName;

I recommend using a leaderlength of 0.3, leaderoffset of 0.1 and a bendstyle of 1. 

You can pass a single statement as an argument to this ULP or the path to a source NDL file

*/

string outputy;
//net definition language

void error(string message)
{
	dlgMessageBox(":" + message);
	exit(1);
}

UL_INSTANCE current_instance;
UL_SHEET current_sheet;
void get_instance(string instance_name)
{
	if (current_instance && current_instance.name == instance_name) 
		return;

	schematic(SCH)
	{
		SCH.sheets(SHEET)
		{
			SHEET.parts(PART)
			{
				if (PART.name == instance_name)
				{
					if (!(current_sheet && SHEET.number == current_sheet.number))
					{
						current_sheet = SHEET;
						sprintf(outputy, "%sEDIT .s%d;\n", outputy, SHEET.number);
					}
			
					PART.instances(INSTANCE)
					{
						current_instance = INSTANCE;
						return;
					}
				}
			}
		}
		string s;
		sprintf(s, "part %s not found!", instance_name);
		error (s);
	}
}

UL_PIN current_pin;
void get_pin(string instance_name, string pin_name)
{
	get_instance(instance_name);

	if (current_pin && current_pin.name == pin_name)
		return;

	current_instance.gate.symbol.pins(PIN)
	{
		if (PIN.name == pin_name)
		{
			current_pin = PIN;
			return;
		}
	}
	string s;
	sprintf(s, "Pin '%s' of part '%s' not found!", pin_name, instance_name);
	error(s);
}

int current_style = -1;
void set_style(int style)
{
	if (current_style != style)
	{
		sprintf(outputy, "%sSET WIRE_BEND %d;\n", outputy, style);
		current_style = style;
	}
}

string current_class = "default";
void set_class(string class)
{
	if (current_class != class)
	{
		sprintf(outputy, "%sCLASS %s;\n", outputy, class);
		current_class = class;
	}
}

void draw_net(UL_PIN pin, string net_name, real length, real offset, int style, string class)
{
	set_style(style);
	set_class(class);

	real offsetx, offsety;
	int angle = pin.angle;
	switch (angle)
	{
		case 0:
			offsetx = -length; offsety = offset;
			break;
		case 90:
		   	offsetx = offset; offsety = -length;
			break;
		case 180:
		   	offsetx = length; offsety = offset;
			break;
		case 270:
		   	offsetx = offset; offsety = length;
		    	break;
	}
	sprintf(outputy, "%sNET %s (%f %f) (%f %f);\n", outputy, net_name, u2mil(pin.x) / 1000, u2mil(pin.y) / 1000, u2mil(pin.x) / 1000 + offsetx, u2mil(pin.y) / 1000 + offsety);
}

int range_start(string range)
{
	string sparts[];
	strsplit(sparts, range, '[');
	strsplit(sparts, sparts[1], '.');
	return strtol(sparts[0]);
}

int range_stop(string range)
{
	string sparts[];
	int part_count = strsplit(sparts, range, '.');
	strsplit(sparts, sparts[part_count - 1], ']');
	return strtol(sparts[0]);
}

void alert(int x)
{
	string s;
	sprintf(s, "%d", x);
	dlgMessageBox(s);
}

string strstrip(string s)
{
	int l = strlen(s);	
	int ifirstchar = 0;
	int ilastchar = 0;
	for (int i = 0; i < l; i++)
	{
		if (s[i] > 0x20)
		{
			ifirstchar = i;
			break;
		}
	}

	for (int j = l - 1; j >= 0; j--)
	{
		if (s[j] > 0x20)
		{
			ilastchar = j;
			break;
		}
	}

	return strsub(s, ifirstchar, ilastchar - ifirstchar + 1);
}

string pin_net_nets = "";
string pin_pin_nets = "";

string write_pin_net_net(string pin, string net, string length, string offset, string style, string class)
{
	sprintf(pin_net_nets, "%s%s %s %s %s %s %s;", pin_net_nets, pin, net, length, offset, style, class);
	return "";
}

string write_pin_pin_net(string pin, string net, string length, string offset, string style, string class)
{
	sprintf(pin_pin_nets, "%s%s %s %s %s %s %s;", pin_pin_nets, pin, net, length, offset, style, class);
	return "Networking pins together is not yet implemented, please specify a net with a pin-list to join pins";
}

int ispin(string pinornet)
{
	return strchr(pinornet, '.') + 1;
}

string write_net(string pinornet1, string pinornet2, string length, string offset, string style, string class)
{
	string sresult = "";
	if (ispin(pinornet1) + ispin(pinornet2) == 0)
		return "Cannot specify 2 nets to be joined. Must have a combination of pin-pin or pin-net";

	if (!ispin(pinornet1))
	{
		sresult = write_pin_net_net(pinornet2, pinornet1, length, offset, style, class);
	}
	else
	{
		if (!ispin(pinornet2))
			sresult = write_pin_net_net(pinornet1, pinornet2, length, offset, style, class);
		else
			sresult = write_pin_pin_net(pinornet1, pinornet2, length, offset, style, class);
	}
	return sresult;
}

string strreplace(string source, string find, string replacement)
{
	int istart = 0;
	int findlength = strlen(find);
	string sresult = source;
	while(1)
	{
		istart = strstr(sresult, find, istart);
		if (istart == -1) break;

		sresult = strsub(sresult, 0, istart) + replacement + strsub(sresult, istart + findlength);
	}
	return sresult;
}

string ltostr(int i)
{
	string s;
	sprintf(s, "%d", i);
	return s;
}

string expand_range(string expression)
{
	string sresult = "";
	if (strchr(expression, '[') > -1)
	{
		int start, stop;
		string iteratorexpression;

		start = strchr(expression, '[');
		stop = strchr(expression, ']', start);
		iteratorexpression = strsub(expression, start, stop - start + 1);

		start = range_start(expression);
		stop = range_stop(expression);
		for (int i = start; i <= stop; i++)
		{
			sresult += strreplace(expression, iteratorexpression, ltostr(i)) + " ";
		}
	}
	else
		sresult = expression;

	return strstrip(sresult);
}

string parse_ndl_instruction(string instruction)
{
	string sparts[],sparts0[],sparts1[];
	int i;

	int part_count = strsplit(sparts, instruction, ' ');

	if (part_count != 6)
		return "Wrong number of elements in instruction. \nExpected format: PinOrNetList1 PinOrNetList2 length offset style class;";

	int part0count = strsplit(sparts0, sparts[0], ',');
	int part1count = strsplit(sparts1, sparts[1], ',');

	string s = "";
	for (i = 0; i < part0count; i++)
	{
		s += expand_range(sparts0[i]) + " ";
	}
	part0count = strsplit(sparts0, strstrip(s), ' ');

	s = "";
	for (i = 0; i < part1count; i++)
	{
		s += expand_range(sparts1[i]) + " ";
	}
	part1count = strsplit(sparts1, strstrip(s), ' ');

	if (part0count > 1 && part1count > 1 && (part0count != part1count))
		return "Mismatch between ranges. When multiple elements need to be mapped to one-another, each argument must contain the same number of elements";

	int partmax = part0count <= part1count ? part1count : part0count;
	if (partmax == 1)
		s = write_net(sparts[0], sparts[1], sparts[2], sparts[3], sparts[4], sparts[5]);

	for (i = 0; i < partmax; i++)
	{
		if (part0count > 1 && part1count > 1)
		{
			s = write_net(sparts0[i], sparts1[i], sparts[2], sparts[3], sparts[4], sparts[5]);
		}
		else
		{
			if (part0count)
				s = write_net(sparts0[i], sparts[1], sparts[2], sparts[3], sparts[4], sparts[5]);
			else
				s = write_net(sparts[0], sparts1[i], sparts[2], sparts[3], sparts[4], sparts[5]);
		}
	}
	if (strlen(s)) return s;

	return "";
}

void parse_ndl(string unparsed_ndl)
{
	unparsed_ndl = strupr(unparsed_ndl);
	
	string slines[];
	string current_instruction = "";
	int line_count = strsplit(slines, unparsed_ndl, '\n');
	char last_char = ' ';
	for (int i_current_line; i_current_line < line_count; i_current_line++)
	{
		int line_length = strlen(slines[i_current_line]);
		for (int i_position; i_position < line_length; i_position++)
		{
			char c = slines[i_current_line][i_position];
			if (c <= 0x20 || c == ' ')
			{
				if (last_char != ' ')
					current_instruction += ' ';

				last_char = ' ';
			}
			else
			{
				if (c == ';')
				{
					string result = parse_ndl_instruction(current_instruction);
					if (strlen(result))
					{
						string serror;
						sprintf(serror, "Instruction error line: %d, position: %d\n\nDescription: %s\n\nInstruction: %s", i_current_line + 1, i_position, result, current_instruction);
						error(serror);
					}
					current_instruction = "";
					last_char = ' ';
				}
				else
				{
					if (isgraph(c))
					{
						current_instruction += c;
						last_char = c;
					}
					else
					{
						string serror;
						sprintf(serror, "Parse error line: %d, position: %d\n\nInvalid character: %c\n\nSource: %s", i_current_line + 1, i_position, c, slines[i_current_line]);
						error(serror);
					}
				}
			}
		}
	}

	string nets[];
	int count = strsplit(nets, pin_net_nets, ';');
	for (int i = 0; i < count - 1; i++)
	{
		string parts[];
		strsplit(parts, strstrip(nets[i]), ' ');
		string part, pin, net, class;
		real length, offset;
		int style;
		string sa[];
		strsplit(sa, parts[0], '.');
		part = sa[0];
		pin = sa[1];
		net = parts[1];
		class = parts[5];
		length = strtod(parts[2]);
		offset = strtod(parts[3]);
		style = strtol(parts[4]);
		get_pin(part, pin);
		draw_net(current_pin, net, length, offset, style, class);
	}
	
}

if (!schematic)
{
	error("This command must be run from the schematic");
}


string x = "";
switch(argc)
{
	case 1: //display dialog
		error ("No arguments specified. \n\nUsage example: \n\nRUN AutoNet IC1.PORTA[0..7] SOMENET[0..6],SomeOtherNet 0.3 0.1 1 default;");
		break;
	case 2: //load file
		fileread(x, argv[1]);
		break;
	default:
		for (int i = 1; i < argc; i++)
		{
			x += argv[i] + " ";
		}
		x = strstrip(x) + ";";
}
parse_ndl(x);

exit(outputy);
